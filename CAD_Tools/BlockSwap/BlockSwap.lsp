;;; BlockSwap.lsp - type BLOCKSWAP to run on the open drawing (RunAll.lsp runs it on a whole folder).
;;; Settings:
(setq BS-DELETE '("TTW_stdCountry_DrgSht_Att_*"))
(setq BS-TEMPLATE "C:/CAD/254166-TTW-00-DR-CV-3546 COREYS TEST TEST TEST DO NOT TOUCH.dwg")
(setq BS-LOG "C:/CAD/BlockSwap.log")
(vl-load-com)
(defun BS:Log (msg / f)
  (princ (strcat "\nBlockSwap: " msg))
  (if BS-LOG (vl-mkdir (vl-filename-directory BS-LOG)))
  (if (and BS-LOG (setq f (open BS-LOG "a")))
    (progn
      (write-line (strcat (getvar "DWGPREFIX") (getvar "DWGNAME") " | " msg) f)
      (close f))))
(defun BS:Match (name patterns)
  (vl-some '(lambda (pat) (wcmatch (strcase name) (strcase pat))) patterns))
(defun BS:EffName (obj / r)
  (setq r (vl-catch-all-apply 'vla-get-EffectiveName (list obj)))
  (if (vl-catch-all-error-p r) (vla-get-Name obj) r))
(defun BS:IsXref (doc ref / def)
  (setq def (vl-catch-all-apply 'vla-Item (list (vla-get-Blocks doc) (vla-get-Name ref))))
  (and (not (vl-catch-all-error-p def)) (= (vla-get-IsXRef def) :vlax-true)))
(defun BS:DeleteBlocks (doc / locked hits n)
  (setq locked '() hits '() n 0)
  (vlax-for lay (vla-get-Layers doc)
    (if (= (vla-get-Lock lay) :vlax-true)
      (progn (setq locked (cons lay locked)) (vla-put-Lock lay :vlax-false))))
  (vlax-for lay (vla-get-Layouts doc)
    (vlax-for ent (vla-get-Block lay)
      (if (and (= (vla-get-ObjectName ent) "AcDbBlockReference")
               (not (BS:IsXref doc ent))
               (BS:Match (BS:EffName ent) BS-DELETE))
        (setq hits (cons ent hits)))))
  (foreach ent hits
    (if (not (vl-catch-all-error-p (vl-catch-all-apply 'vla-Delete (list ent))))
      (setq n (1+ n))))
  (foreach lay locked (vla-put-Lock lay :vlax-true))
  n)
(defun BS:OpenTemplate (path / dbx)
  (setq dbx (vla-GetInterfaceObject (vlax-get-acad-object)
              (strcat "ObjectDBX.AxDbDocument." (substr (getvar "ACADVER") 1 2))))
  (if (vl-catch-all-error-p (vl-catch-all-apply 'vla-Open (list dbx path)))
    (progn (vlax-release-object dbx) nil)
    dbx))
(defun BS:TargetLayout (doc name / lay first)
  (setq lay (vl-catch-all-apply 'vla-Item (list (vla-get-Layouts doc) name)))
  (if (vl-catch-all-error-p lay)
    (progn
      (vlax-for l (vla-get-Layouts doc)
        (if (and (/= (strcase (vla-get-Name l)) "MODEL")
                 (or (not first) (< (vla-get-TabOrder l) (vla-get-TabOrder first))))
          (setq first l)))
      (if first (BS:Log (strcat "no layout \"" name "\", using \"" (vla-get-Name first) "\"")))
      first)
    lay))
(defun BS:CopyFromTemplate (doc / dbx objs arr target n res)
  (setq n 0)
  (cond
    ((not BS-TEMPLATE) (BS:Log "BS-TEMPLATE is nil - copy step skipped"))
    ((not (findfile BS-TEMPLATE)) (BS:Log (strcat "CAN'T FIND TEMPLATE " BS-TEMPLATE)))
    ((not (setq dbx (BS:OpenTemplate (findfile BS-TEMPLATE)))) (BS:Log (strcat "COULD NOT OPEN TEMPLATE (is it open?) " BS-TEMPLATE)))
    (t
      (vlax-for tlay (vla-get-Layouts dbx)
        (setq objs '())
        (vlax-for ent (vla-get-Block tlay)
          (if (and (= (vla-get-ObjectName ent) "AcDbBlockReference")
                   (BS:Match (BS:EffName ent) BS-DELETE))
            (setq objs (cons ent objs))))
        (if objs
          (if (setq target (BS:TargetLayout doc (vla-get-Name tlay)))
            (progn
              (setq arr (vlax-make-safearray vlax-vbObject (cons 0 (1- (length objs)))))
              (vlax-safearray-fill arr (reverse objs))
              (if (vl-catch-all-error-p
                    (setq res (vl-catch-all-apply 'vla-CopyObjects (list dbx arr (vla-get-Block target)))))
                (BS:Log (strcat "ERROR copying into \"" (vla-get-Name target) "\": " (vl-catch-all-error-message res)))
                (progn
                  (setq n (+ n (length objs)))
                  (BS:Log (strcat "copied " (itoa (length objs)) " block(s) from template \"" (vla-get-Name tlay) "\" into \"" (vla-get-Name target) "\"")))))
            (BS:Log (strcat "no layout to copy \"" (vla-get-Name tlay) "\" blocks into")))))
      (vlax-release-object dbx)))
  n)
(defun BS:Run (/ doc del ins)
  (setq doc (vla-get-ActiveDocument (vlax-get-acad-object)))
  (if (and BS-TEMPLATE
           (= (strcase (strcat (getvar "DWGPREFIX") (getvar "DWGNAME"))) (strcase (cond ((findfile BS-TEMPLATE)) ("")))))
    (BS:Log "this is the template drawing - skipped")
    (progn
      (vla-StartUndoMark doc)
      (setq del (BS:DeleteBlocks doc))
      (BS:Log (strcat "deleted " (itoa del) " TTW_stdCountry_DrgSht_Att_ block(s)"))
      (repeat 3 (vla-PurgeAll doc))
      (setq ins (BS:CopyFromTemplate doc))
      (vla-EndUndoMark doc)
      (BS:Log (strcat "DONE: deleted " (itoa del) ", copied in " (itoa ins)))))
  (princ))
(defun c:BLOCKSWAP () (BS:Run))
(princ "\nBlockSwap loaded. Type BLOCKSWAP.")
(princ)
